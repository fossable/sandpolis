SANDPOLIS-MIB DEFINITIONS ::= BEGIN

IMPORTS
	enterprises,
	IpAddress,
	TimeTicks
		FROM RFC1155-SMI
	OBJECT-TYPE
		FROM RFC-1212;


attribute OBJECT IDENTIFIER
	::= { enterprises 55444 }

sndInstance OBJECT IDENTIFIER
	::= { attribute 1 }

sndInstanceType OBJECT-TYPE
	SYNTAX INTEGER {
		CHARCOAL(0),
		SERVER(1),
		CLIENT(2),
		VIEWER(3),
		INSTALLER(4)
	}
	ACCESS  read-only
	STATUS  current
	DESCRIPTION
		"The instance's broad type."
	::= { sndInstance 1 }

sndInstanceFlavor OBJECT-TYPE
	SYNTAX INTEGER {
		NONE(0),
		VANILLA(1),
		MEGA(2),
		MICRO(3),
		ASCETIC(4),
		LIFEGEM(5),
		SOAPSTONE(6),
		LOCKSTONE(7)
	}
	ACCESS  read-only
	STATUS  current
	DESCRIPTION
		"The instance's subtype."
	::= { sndInstance 2 }

sndInstanceCvid OBJECT-TYPE
	SYNTAX  INTEGER
	ACCESS  read-only
	STATUS  current
	DESCRIPTION
		"The instance's Client/Viewer ID (CVID)."
	::= { sndInstance 3 }

sndInstanceUuid OBJECT-TYPE
	SYNTAX  OCTET STRING
	ACCESS  read-only
	STATUS  current
	DESCRIPTION
		"The instance's Universally Unique ID (UUID)."
	::= { sndInstance 4 }

sndInstanceVersion OBJECT-TYPE
	SYNTAX  OCTET STRING
	ACCESS  read-only
	STATUS  current
	DESCRIPTION
		"The instance's Sandpolis version string."
	::= { sndInstance 5 }

sndClient OBJECT IDENTIFIER
	::= { attribute 2 }

sndClientInstallPath OBJECT-TYPE
	SYNTAX  OCTET STRING
	ACCESS  read-only
	STATUS  current
	DESCRIPTION
		"The client's installation path."
	::= { sndClient 1 }

sndViewer OBJECT IDENTIFIER
	::= { attribute 3 }

sndViewerUsername OBJECT-TYPE
	SYNTAX  OCTET STRING
	ACCESS  read-only
	STATUS  current
	DESCRIPTION ""
	::= { sndViewer 1 }

sndViewerLogins OBJECT-TYPE
	SYNTAX  SEQUENCE OF SndLoginEntry
	ACCESS  not-accessible
	STATUS  mandatory
	DESCRIPTION ""
	::= { sndViewer 2 }

sndLoginEntry OBJECT-TYPE
	SYNTAX  SndLoginEntry
	ACCESS  not-accessible
	STATUS  mandatory
	DESCRIPTION ""
	INDEX {
		sndEntryIndex }
	::= { sndViewerLogins 1 }

SndLoginEntry ::= SEQUENCE {

	sndEntryIp    IpAddress,
	sndEntryTime  TimeTicks,
	sndEntryIndex INTEGER }

sndEntryIp OBJECT-TYPE
	SYNTAX  IpAddress
	ACCESS  read-only
	STATUS  mandatory
	DESCRIPTION
		""
	::= { sndLoginEntry 1 }


sndEntryTime OBJECT-TYPE
	SYNTAX  TimeTicks
	ACCESS  read-only
	STATUS  mandatory
	DESCRIPTION
		""
	::= { sndLoginEntry 2 }


sndEntryIndex OBJECT-TYPE
	SYNTAX  INTEGER (0..10000)
	ACCESS  read-only
	STATUS  mandatory
	DESCRIPTION
		""
	::= { sndLoginEntry 3 }

sndServer OBJECT IDENTIFIER
	::= { attribute 4 }

END
